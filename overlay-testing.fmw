FME workspace overlay-testing.fmw

Parameters:
- DestDataset_CSV2 = C:\Users\tacree1\Desktop\it-conference-2019\demo   # Destination CSV (Comma Separated Value) Folder
- SourceDataset_XLSXR = $(FME_MF_DIR)data.xlsx   # Source Microsoft Excel File(s)
- DestDataset_XLSXW = $(FME_MF_DIR)errors.xlsx   # Destination Microsoft Excel File

Readers:
- XLSXR_1: XLSXR from $(SourceDataset_XLSXR)

Writers:
- CSV2_1: CSV2 to $(DestDataset_CSV2)
- XLSXW_1: XLSXW to $(DestDataset_XLSXW)

COUNTY (reader XLSXR_1)
    attributes: COUNTY_ID number(7,0), NLF_ID char(15), MEASURE_FROM number(5,2), MEASURE_TO number(5,2), COUNTY char(4), RH_DATE_RETIRE string
    -> LrsMeasureVertexCreatorCounty [BeginVertexCreator_Input]
Note: Read the data from each table and turn their measures into a linear geometry
LrsMeasureVertexCreatorCounty
    _BEGIN_MEASURE = @Value(MEASURE_FROM)
    _END_MEASURE = @Value(MEASURE_TO)
    EndVertexCreator_Output -> LineOnLineOverlayer [LINE]
MILEAGE_ALLOC (reader XLSXR_1)
    attributes: MILEAGE_ALLOCATION_ID char(37), NLF_ID char(15), MEASURE_FROM number(5,2), MEASURE_TO number(5,2), COUNTY_CODE char(4), OVERLAP_INDICATOR char(2)
    -> LrsMeasureVertexCreatorMilAlloc [BeginVertexCreator_Input]
LrsMeasureVertexCreatorMilAlloc
    _BEGIN_MEASURE = @Value(MEASURE_FROM)
    _END_MEASURE = @Value(MEASURE_TO)
    EndVertexCreator_Output -> LineOnLineOverlayer [LINE]
Note: Merge the data based on NLF_ID matches and / intersecting segmentation
LineOnLineOverlayer
    ATTRS_ACCUM_MODE = Merge Attributes
    CLEANING_TOLERANCE = None
    DEAGGREGATE_INPUT = Yes
    GENERATE_LIST_DROP = NO
    GROUP_BY = NLF_ID
    OV_ATTR = _overlaps
    SEPARATE_COLLINEAR_SEGMENTS = No
    LINE -> LrsExtractMeasuresFromCoord [CopyCoordToBegin_Input]
    LINE -> OverlaySorter
Note: move measures from coordinates back to measure / attributes
LrsExtractMeasuresFromCoord
    _BEGIN_MEASURE_FIELD = MEASURE_FROM
    _END_MEASURE_FIELD = MEASURE_TO
    CopyCoordToEnd_Output -> AttributeManager
Note: Create custom ERROR_CODE attribute / and populate it.
AttributeManager
    ATTR_TABLE = SET_TO ERROR_CODE = FME_CONDITIONAL:DEFAULT_VALUE'VALID'BOOL_OP;AND;COMPOSITE_TEST;<Unused>;TEST COUNTY_ID ATTRIBUTE_IS_MISSING _FME_BLANK_STRING_;TEST @Value(OVERLAP_INDICATOR) = P'MISSING_COUNTY_PRIMARY'BOOL_OP;AND;COMPOSITE_TEST;1 AND 2;TEST COUNTY_ID ATTRIBUTE_HAS_A_VALUE _FME_BLANK_STRING_;TEST @Value(OVERLAP_INDICATOR) = S'COUNTY_ON_SECONDARY'BOOL_OP;AND;COMPOSITE_TEST;1 AND 2;TEST COUNTY_ID ATTRIBUTE_HAS_A_VALUE _FME_BLANK_STRING_;TEST OVERLAP_INDICATOR ATTRIBUTE_IS_MISSING _FME_BLANK_STRING_'EXTRA_COUNTY_RECORD'FME_NUM_CONDITIONS4___
    -> ResultSorter
ResultSorter: Sorter
    SORT_PARM = NLF_ID ALPHA ASCENDING MEASURE_FROM NUMERIC ASCENDING
    SORTED -> allResults
    SORTED -> TestFilter
TestFilter
    DEFAULT_VALUE = <UNFILTERED>
    TEST_LIST = "BOOL_OP,OR,COMPOSITE_TEST,""""""1"""""",TEST_CLAUSE,TEST @Value(ERROR_CODE) != VALID",@Value(ERROR_CODE) != VALID
    @Value(ERROR_CODE) != VALID -> errors (writer XLSXW_1)
    @Value(ERROR_CODE) != VALID -> errorsOutput
    <UNFILTERED> -> ValidOutput
errors (writer XLSXW_1)
    attributes: MILEAGE_ALLOCATION_ID string(37), NLF_ID string(15), MEASURE_FROM number(5), MEASURE_TO number(5), OVERLAP_INDICATOR string(2), COUNTY_ID number(7), COUNTY string(4), _overlaps auto(20), ERROR_CODE auto(20)
errorsOutput: Inspector
ValidOutput: Inspector
allResults: Inspector
OverlaySorter: Sorter
    SORT_PARM = NLF_ID ALPHA ASCENDING MEASURE_FROM NUMERIC ASCENDING
    SORTED -> Overlay_Output
Note: Show data after overlay but before extracting measures / from coordiinates
Overlay_Output: Inspector

FME custom transformer LrsMeasureVertexCreator

Parameters:
- _BEGIN_MEASURE =   # Begin Measure
- _END_MEASURE =   # End Measure

BeginVertexCreator_Input (input)
    -> GeometryRemover
GeometryRemover
    -> BeginVertexCreator
BeginVertexCreator: VertexCreator
    MEASURE_TYPE = Continuous
    MISSING_VAL_MODE = None (Drop Values)
    MODE_NAME = Add Point
    XVAL = @Value(_Begin_Measure)
    YVAL = 0
    -> EndVertexCreator
EndVertexCreator: VertexCreator
    MEASURE_TYPE = Continuous
    MISSING_VAL_MODE = None (Drop Values)
    MODE_NAME = Add Point
    XVAL = @Value(_End_Measure)
    YVAL = 0
    -> AttributeRemover
AttributeRemover
    REMOVE_ATTRS = _End_Measure,_Begin_Measure
    -> EndVertexCreator_Output (output)
EndVertexCreator_Output (output)

FME custom transformer LrsExtractMeasuresFromCoord

Parameters:
- _BEGIN_MEASURE_FIELD =   # "" Begin Measure Field
- _END_MEASURE_FIELD =   # "" End Measure Field

CopyCoordToBegin_Input (input)
    -> CopyCoordToBegin
CopyCoordToBegin: CoordinateExtractor
    IND = 0
    MODE = Specify Coordinate
    X_ATTR = $(_BEGIN_MEASURE_FIELD)
    -> CopyCoordToEnd
CopyCoordToEnd: CoordinateExtractor
    IND = -1
    MODE = Specify Coordinate
    X_ATTR = $(_END_MEASURE_FIELD)
    -> AttributeRemover
AttributeRemover
    REMOVE_ATTRS = _Begin_Measure_Field,_End_Measure_Field
    -> CopyCoordToEnd_Output (output)
CopyCoordToEnd_Output (output)
